# -*- coding: utf-8 -*-

# Macro Begin: /home/alexandre/.FreeCAD/pentalobeScrew.FCMacro +++++++++++++++++++++++++++++++++++++++++++++++++
import FreeCAD
import Sketcher

mySketch = App.activeDocument().addObject('Sketcher::SketchObject','Sketch_P001')

mySketch.addGeometry(Part.Circle(App.Vector(0.957230,1.202942,0),App.Vector(0,0,1),2.241391),True)
mySketch.addGeometry(Part.ArcOfCircle(Part.Circle(App.Vector(0.999921,3.508269,0),App.Vector(0,0,1),1.485017),-6.704605,-2.819842),False)
mySketch.addConstraint(Sketcher.Constraint('PointOnObject',1,3,0)) 
mySketch.addConstraint(Sketcher.Constraint('PointOnObject',1,2,0)) 
mySketch.addConstraint(Sketcher.Constraint('PointOnObject',1,1,0)) 
mySketch.addGeometry(Part.ArcOfCircle(Part.Circle(App.Vector(3.134483,1.587163,0),App.Vector(0,0,1),1.527813),-1.771449,2.105750),False)
mySketch.addConstraint(Sketcher.Constraint('PointOnObject',2,3,0)) 
mySketch.addConstraint(Sketcher.Constraint('Coincident',2,2,1,1)) 
mySketch.addConstraint(Sketcher.Constraint('PointOnObject',2,1,0)) 
mySketch.addGeometry(Part.ArcOfCircle(Part.Circle(App.Vector(2.081547,-0.687647,0),App.Vector(0,0,1),1.079298),-2.843094,0.804544),False)
mySketch.addConstraint(Sketcher.Constraint('PointOnObject',3,3,0)) 
mySketch.addConstraint(Sketcher.Constraint('Coincident',3,2,2,1)) 
mySketch.addConstraint(Sketcher.Constraint('PointOnObject',3,1,0)) 
mySketch.addGeometry(Part.ArcOfCircle(Part.Circle(App.Vector(-0.665664,-0.387171,0),App.Vector(0,0,1),1.823514),-4.321341,-0.345685),False)
mySketch.addConstraint(Sketcher.Constraint('PointOnObject',4,3,0)) 
mySketch.addConstraint(Sketcher.Constraint('Coincident',4,2,3,1)) 
mySketch.addConstraint(Sketcher.Constraint('PointOnObject',4,1,0)) 
mySketch.addGeometry(Part.ArcOfCircle(Part.Circle(App.Vector(-1.094917,2.360041,0),App.Vector(0,0,1),1.117522),-5.495068,-1.803353),False)
mySketch.addConstraint(Sketcher.Constraint('PointOnObject',5,3,0)) 
mySketch.addConstraint(Sketcher.Constraint('Coincident',5,2,4,1)) 
mySketch.addConstraint(Sketcher.Constraint('Coincident',5,1,1,2)) 
mySketch.addConstraint(Sketcher.Constraint('Equal',5,1)) 
mySketch.addConstraint(Sketcher.Constraint('Equal',1,2)) 
mySketch.addConstraint(Sketcher.Constraint('Equal',2,3)) 
mySketch.addConstraint(Sketcher.Constraint('Equal',3,4)) 

FreeCAD.Console.PrintMessage("- Finish -")

#Gui.getDocument('Sans_nom').resetEdit()
#App.getDocument('Sans_nom').recompute()
# Macro End: /home/alexandre/.FreeCAD/pentalobeScrew.FCMacro +++++++++++++++++++++++++++++++++++++++++++++++++
