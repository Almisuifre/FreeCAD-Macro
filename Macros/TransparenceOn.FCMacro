# -*- coding: utf-8 -*-

# Merci à Yorick pour sa correction

# Macro Begin: /home/alexandre/.FreeCAD/TransparenceOn.FCMacro +++++++++++++++++++++++++++++++++++++++++++++++++
import FreeCAD

sel = FreeCADGui.Selection.getSelection()
doc = App.activeDocument()

operation = sel[0].Name

if hasattr( FreeCADGui.getDocument(doc).getObject(operation), "Transparency" ) :
	FreeCADGui.getDocument(doc).getObject(operation).Transparency = 50

# Macro End: /home/alexandre/.FreeCAD/TransparenceOn.FCMacro +++++++++++++++++++++++++++++++++++++++++++++++++
